module ODL-skeleton-impl-config {
   yang-version 1;
   namespace "urn:opendaylight:params:xml:ns:yang:ODL-skeleton:impl:config";
   prefix "ODL-skeleton-impl-config";
   import config { prefix config; revision-date 2013-04-05; }
   import opendaylight-md-sal-binding { prefix md-sal-binding; revision-date 2013-10-28;}
   description
       "Service definition for ODL-skeleton project";
   revision "2014-12-10" {
       description
           "Initial revision";
   }
   identity ODL-skeleton-impl-config {
       base config:module-type;
       config:java-name-prefix ODL-skeletonImpl;
   }
   augment "/config:modules/config:module/config:configuration" {
       case ODL-skeleton-impl-config {
           when "/config:modules/config:module/config:type = 'ODL-skeleton-impl-config'";
           container binding-aware-broker {
               uses config:service-ref {
                   refine type {
                       mandatory true;
                       config:required-identity md-sal-binding:binding-broker-osgi-registry;
                   }
               }
           }
       }
   }
}
